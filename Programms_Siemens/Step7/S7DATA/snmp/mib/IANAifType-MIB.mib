----------------------------------------------------------------------------------------------------
-- SIEMENS AG   MIB for MIB Compiler OPC SNMP Server SIMATIC NET
-- IANAifType-MIB.mib
-- RFC  1573
-- Version: 1.0
-- Date: 23.04.2002
-- Comment: Convert to SMIv1
----------------------------------------------------------------------------------------------------

IANAifType-MIB DEFINITIONS ::= BEGIN

IMPORTS
    mib-2
            FROM SNMPv2-SMI-v1;

ianaifType OBJECT IDENTIFIER ::= { mib-2 30 }
-- MODULE-IDENTITY
--  LastUpdated
--    200109190000Z
--  OrgName
--    IANA
--  ContactInfo
--            Internet Assigned Numbers Authority
--    
--     Postal: ICANN
--             4676 Admiralty Way, Suite 330
--             Marina del Rey, CA 90292
--    
--     Tel:    +1 310 823 9358
--     E-Mail: iana@iana.org
--  Descr
--    This MIB module defines the IANAifType Textual
--     Convention, and thus the enumerated values of
--     the ifType object defined in MIB-II's ifTable.
--  RevDate
--    200109190000Z
--  RevDescr
--    Registration of new IANAifType
--    198.
--  RevDate
--    200105110000Z
--  RevDescr
--    Registration of new IANAifType
--    197.
--  RevDate
--    200101120000Z
--  RevDescr
--    Registration of new IANAifTypes
--    195 and 196.
--  RevDate
--    200012190000Z
--  RevDescr
--    Registration of new IANAifTypes
--    193 and 194.
--  RevDate
--    200012070000Z
--  RevDescr
--    Registration of new IANAifTypes
--    191 and 192.
--  RevDate
--    200012040000Z
--  RevDescr
--    Registration of new IANAifType
--    190.
--  RevDate
--    200010170000Z
--  RevDescr
--    Registration of new IANAifTypes
--    188 and 189.
--  RevDate
--    200010020000Z
--  RevDescr
--    Registration of new IANAifType 187.
--  RevDate
--    200009010000Z
--  RevDescr
--    Registration of new IANAifTypes
--     184, 185, and 186.
--  RevDate
--    200008240000Z
--  RevDescr
--    Registration of new IANAifType 183.
--  RevDate
--    200008230000Z
--  RevDescr
--    Registration of new IANAifTypes
--     174-182.
--  RevDate
--    200008220000Z
--  RevDescr
--    Registration of new IANAifTypes 170,
--     171, 172 and 173.
--  RevDate
--    200004250000Z
--  RevDescr
--    Registration of new IANAifTypes 168 and 169.
--  RevDate
--    200003060000Z
--  RevDescr
--    Fixed a missing semi-colon in the IMPORT.
--     Also cleaned up the REVISION log a bit.
--     It is not complete, but from now on it will
--     be maintained and kept up to date with each
--     change to this MIB module.
--  RevDate
--    199910081430Z
--  RevDescr
--    Include new name assignments up to cnr(85).
--     This is the first version available via the WWW
--     at: ftp://ftp.isi.edu/mib/ianaiftype.mib
--  RevDate
--    199401310000Z
--  RevDescr
--    Initial version of this MIB as published in
--     RFC 1573.

IANAifType ::= INTEGER {
        other(1),
        regular1822(2),
        hdh1822(3),
        ddnX25(4),
        rfc877x25(5),
        ethernetCsmacd(6),
        iso88023Csmacd(7),
        iso88024TokenBus(8),
        iso88025TokenRing(9),
        iso88026Man(10),
        starLan(11),
        proteon10Mbit(12),
        proteon80Mbit(13),
        hyperchannel(14),
        fddi(15),
        lapb(16),
        sdlc(17),
        ds1(18),
        e1(19),
        basicISDN(20),
        primaryISDN(21),
        propPointToPointSerial(22),
        ppp(23),
        softwareLoopback(24),
        eon(25),
        ethernet3Mbit(26),
        nsip(27),
        slip(28),
        ultra(29),
        ds3(30),
        sip(31),
        frameRelay(32),
        rs232(33),
        para(34),
        arcnet(35),
        arcnetPlus(36),
        atm(37),
        miox25(38),
        sonet(39),
        x25ple(40),
        iso88022llc(41),
        localTalk(42),
        smdsDxi(43),
        frameRelayService(44),
        v35(45),
        hssi(46),
        hippi(47),
        modem(48),
        aal5(49),
        sonetPath(50),
        sonetVT(51),
        smdsIcip(52),
        propVirtual(53),
        propMultiplexor(54),
        ieee80212(55),
        fibreChannel(56),
        hippiInterface(57),
        frameRelayInterconnect(58),
        aflane8023(59),
        aflane8025(60),
        cctEmul(61),
        fastEther(62),
        isdn(63),
        v11(64),
        v36(65),
        g703at64k(66),
        g703at2mb(67),
        qllc(68),
        fastEtherFX(69),
        channel(70),
        ieee80211(71),
        ibm370parChan(72),
        escon(73),
        dlsw(74),
        isdns(75),
        isdnu(76),
        lapd(77),
        ipSwitch(78),
        rsrb(79),
        atmLogical(80),
        ds0(81),
        ds0Bundle(82),
        bsc(83),
        async(84),
        cnr(85),
        iso88025Dtr(86),
        eplrs(87),
        arap(88),
        propCnls(89),
        hostPad(90),
        termPad(91),
        frameRelayMPI(92),
        x213(93),
        adsl(94),
        radsl(95),
        sdsl(96),
        vdsl(97),
        iso88025CRFPInt(98),
        myrinet(99),
        voiceEM(100),
        voiceFXO(101),
        voiceFXS(102),
        voiceEncap(103),
        voiceOverIp(104),
        atmDxi(105),
        atmFuni(106),
        atmIma(107),
        pppMultilinkBundle(108),
        ipOverCdlc(109),
        ipOverClaw(110),
        stackToStack(111),
        virtualIpAddress(112),
        mpc(113),
        ipOverAtm(114),
        iso88025Fiber(115),
        tdlc(116),
        gigabitEthernet(117),
        hdlc(118),
        lapf(119),
        v37(120),
        x25mlp(121),
        x25huntGroup(122),
        trasnpHdlc(123),
        interleave(124),
        fast(125),
        ip(126),
        docsCableMaclayer(127),
        docsCableDownstream(128),
        docsCableUpstream(129),
        a12MppSwitch(130),
        tunnel(131),
        coffee(132),
        ces(133),
        atmSubInterface(134),
        l2vlan(135),
        l3ipvlan(136),
        l3ipxvlan(137),
        digitalPowerline(138),
        mediaMailOverIp(139),
        dtm(140),
        dcn(141),
        ipForward(142),
        msdsl(143),
        ieee1394(144),
        if-gsn(145),
        dvbRccMacLayer(146),
        dvbRccDownstream(147),
        dvbRccUpstream(148),
        atmVirtual(149),
        mplsTunnel(150),
        srp(151),
        voiceOverAtm(152),
        voiceOverFrameRelay(153),
        idsl(154),
        compositeLink(155),
        ss7SigLink(156),
        propWirelessP2P(157),
        frForward(158),
        rfc1483(159),
        usb(160),
        ieee8023adLag(161),
        bgppolicyaccounting(162),
        frf16MfrBundle(163),
        h323Gatekeeper(164),
        h323Proxy(165),
        mpls(166),
        mfSigLink(167),
        hdsl2(168),
        shdsl(169),
        ds1FDL(170),
        pos(171),
        dvbAsiIn(172),
        dvbAsiOut(173),
        plc(174),
        nfas(175),
        tr008(176),
        gr303RDT(177),
        gr303IDT(178),
        isup(179),
        propDocsWirelessMaclayer(180),
        propDocsWirelessDownstream(181),
        propDocsWirelessUpstream(182),
        hiperlan2(183),
        propBWAp2Mp(184),
        sonetOverheadChannel(185),
        digitalWrapperOverheadChannel(186),
        aal2(187),
        radioMAC(188),
        atmRadio(189),
        imt(190),
        mvl(191),
        reachDSL(192),
        frDlciEndPt(193),
        atmVciEndPt(194),
        opticalChannel(195),
        opticalTransport(196),
        propAtm(197),
        voiceOverCable(198)
        }
-- TEXTUAL-CONVENTION
--  Status
--    mandatory
--  Descr
--    This data type is used as the syntax of the ifType
--    object in the (updated) definition of MIB-II's
--    ifTable.
--    
--    The definition of this textual convention with the
--    addition of newly assigned values is published
--    periodically by the IANA, in either the Assigned
--    Numbers RFC, or some derivative of it specific to
--    Internet Network Management number assignments.  (The
--    latest arrangements can be obtained by contacting the
--    IANA.)
--    
--    Requests for new values should be made to IANA via
--    email (iana@iana.org).
--    
--    The relationship between the assignment of ifType
--    values and of OIDs to particular media-specific MIBs
--    is solely the purview of IANA and is subject to change
--    without notice.  Quite often, a media-specific MIB's
--    OID-subtree assignment within MIB-II's 'transmission'
--    subtree will be the same as its ifType value.
--    However, in some circumstances this will not be the
--    case, and implementors must not pre-assume any
--    specific relationship between ifType values and
--    transmission subtree OIDs.


END
