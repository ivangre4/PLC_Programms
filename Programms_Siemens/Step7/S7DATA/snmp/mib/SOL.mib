----------------------------------------------------------------------------
--                       Safecard On LAN - SOL
----------------------------------------------------------------------------
-- Title:        SOL Management Information Base
-- Version:      2.2.0.2
-- Author:       Peter Tucholski, Siemens AG, Karlsruhe

-- Description:  This MIB exports the functionality of the Siematic DiagMonitor
--               to SNMP.
-- Syntax:       IETF RFC 1155.

-- History       ddmmyyyy Version Subject of Change    Author
--		 		 11102005 2.2.0.2    created     		Peter Tucholski


----------------------------------------------------------------------------

SOL-MIB DEFINITIONS ::= BEGIN

         IMPORTS
                 enterprises
                         FROM RFC1155-SMI
                 OBJECT-TYPE
                         FROM RFC-1212
                 DisplayString
                         FROM RFC-1213;

-- SOL tree structure definition

-- the following should reside in the simaticPC (ad, adProductMibs) MIB
         ad              OBJECT IDENTIFIER ::= { enterprises 4196 }
		 adProductMibs   OBJECT IDENTIFIER ::= { ad 1 }
		 simaticPC       OBJECT IDENTIFIER ::= { adProductMibs 2 }

-- now this is SOL
         sol             OBJECT IDENTIFIER ::= { simaticPC 1 }

-- SOL system info
		 solSystem           		OBJECT IDENTIFIER ::= { sol 1 }       -- system info
		 solSystemType       		OBJECT IDENTIFIER ::= { solSystem 1 } -- system type
		 solSystemStatus     		OBJECT IDENTIFIER ::= { solSystem 2 } -- system status
		 solSystemWatchdog   		OBJECT IDENTIFIER ::= { solSystem 3 } -- system watchdog
		 solSystemHeartbeat  		OBJECT IDENTIFIER ::= { solSystem 4 } -- system heartbeat
		 solSystemInterrupt  		OBJECT IDENTIFIER ::= { solSystem 5 }
		 solSystemHibernate  		OBJECT IDENTIFIER ::= { solSystem 6 } -- system hibernate
		 solSystemOperatingHours  	OBJECT IDENTIFIER ::= { solSystem 7 } -- system operating hours
		 solSystemDriverFiles	  	OBJECT IDENTIFIER ::= { solSystem 8 } -- system driver files
		 solSystemProductInfo		OBJECT IDENTIFIER ::= { solSystem 11 } -- system product information

		 solSensor       OBJECT IDENTIFIER ::= { sol 2 }    -- sensor info
		 solDisc         OBJECT IDENTIFIER ::= { sol 3 }    -- disc info

		 solEnd			 OBJECT IDENTIFIER ::= { sol 10 }   -- just to mark the end for convenience

---------------------------------------------
-- System
---------------------------------------------

    name         OBJECT-TYPE
                 SYNTAX       DisplayString
                 ACCESS       read-only
                 STATUS       mandatory
                 DESCRIPTION  "System name"
                 ::=          { solSystemType 1 }

-- status
    statusValue OBJECT-TYPE
                 SYNTAX       INTEGER
                 ACCESS       read-write
                 STATUS       mandatory
                 DESCRIPTION  "Status value, set this value to 0 to reset status"
                 ::=          { solSystemStatus 1 }

-- watchdog
    watchdogActive OBJECT-TYPE
                 SYNTAX       INTEGER (0..1)
                 ACCESS       read-write
                 STATUS       mandatory
                 DESCRIPTION  "Is watchdog activated?. Set this value to 1/0 to
				               activate/deactivate the watchdog."
                 ::=          { solSystemWatchdog 1 }

    watchdogTime OBJECT-TYPE
                 SYNTAX       INTEGER (3..255)
                 ACCESS       read-write
                 STATUS       mandatory
                 DESCRIPTION  "Watchdog interval in seconds."
                 ::=          { solSystemWatchdog 2 }

    watchdogResetEnable OBJECT-TYPE
                 SYNTAX       INTEGER (0..1)
                 ACCESS       read-write
                 STATUS       mandatory
                 DESCRIPTION  "Is watchdog reset enabled?. If activated then a watchdog
				               timeout will hard-reset the system. Set this value
							   to 1/0 to activate/deactivate the automatic reset."
                 ::=          { solSystemWatchdog 3 }

-- heartbeat
    heartbeatInterval OBJECT-TYPE
                 SYNTAX       INTEGER (1..255)
                 ACCESS       read-write
                 STATUS       mandatory
                 DESCRIPTION  "Heartbeat interval in seconds."
                 ::=          { solSystemHeartbeat 1 }

    heartbeatEnable OBJECT-TYPE
                 SYNTAX       INTEGER (0..1)
                 ACCESS       read-write
                 STATUS       mandatory
                 DESCRIPTION  "Is heartbeat activated? Set this value to 1/0 to
				               activate/deactivate the heartbeat. If activated then
							   a heartbeat trap will be triggered every heartbeat interval."
                 ::=          { solSystemHeartbeat 2 }

-- interrupt
    interruptActive    OBJECT-TYPE
                 SYNTAX       INTEGER (0..1)
                 ACCESS       read-write
                 STATUS       mandatory
                 DESCRIPTION  "Is interrupt activatec? Set this value to 1/0 to
				               activate/deactivate the interrupt. If activated then
							   an interrupt trap will be triggered on every SOM
							   interrupt."
                 ::=          { solSystemInterrupt 1 }

-- hibernate
    systemHibernate    OBJECT-TYPE
                 SYNTAX       INTEGER (0..255)
                 ACCESS       read-write
                 STATUS       mandatory
                 DESCRIPTION  "Is hibernate activated? Set this value is initially 0 if the system
				               doesn't support hibernate mode. Switch bit 1 to toggle
							   between enable/disable hibernate"
                 ::=          { solSystemHibernate 0 }
                 
-- operating hours
	systemOperatingHours OBJECT-TYPE
				SYNTAX		INTEGER
				ACCESS		read-only
				STATUS		mandatory
				DESCRIPTION "Total Operating Hours Count"
				::=			{ solSystemOperatingHours 1 }
				
	systemRevisionHours OBJECT-TYPE
				SYNTAX		INTEGER
				ACCESS		read-only
				STATUS		mandatory
				DESCRIPTION "Operating Hours at Time of Alert. Used only when Revision Trap occurs"
				::=			{ solSystemOperatingHours 2 }
				
	systemRevisionText OBJECT-TYPE
				SYNTAX		OCTET STRING (SIZE(80))
				ACCESS		read-only
				STATUS		mandatory
				DESCRIPTION "Text Description. Used only when Revision Trap occurs"
				::=			{ solSystemOperatingHours 3 }

-- driver files				
	systemDriverFileName OBJECT-TYPE
				SYNTAX		OCTET STRING (SIZE(255))
				ACCESS		read-only
				STATUS		mandatory
				DESCRIPTION "Driver File Name"
				::=			{ solSystemDriverFiles 1 }
							
	systemDriverVersion OBJECT-TYPE
				SYNTAX		OCTET STRING (SIZE(32))
				ACCESS		read-only
				STATUS		mandatory
				DESCRIPTION "Driver Version String"
				::=			{ solSystemDriverFiles 2 }

	systemDriverFileIndex OBJECT-TYPE
				SYNTAX		INTEGER
				ACCESS		read-write
				STATUS		mandatory
				DESCRIPTION "Index of queried Driver File"
				::=			{ solSystemDriverFiles 3 }				
	
-- Product Information
	ProductName OBJECT-TYPE
				SYNTAX		OCTET STRING (SIZE(255))
				ACCESS		read-only
				STATUS		mandatory
				DESCRIPTION "Product Name"
				::=			{ solSystemProductInfo 1 }
				
	Manufacturer OBJECT-TYPE
				SYNTAX		OCTET STRING (SIZE(255))
				ACCESS		read-only
				STATUS		mandatory
				DESCRIPTION "Product Manufacturer"
				::=			{ solSystemProductInfo 2 }
				
	SystemVersion OBJECT-TYPE
				SYNTAX		OCTET STRING (SIZE(255))
				ACCESS		read-only
				STATUS		mandatory
				DESCRIPTION "System Version"
				::=			{ solSystemProductInfo 3 }
				
	SerialNumber OBJECT-TYPE
				SYNTAX		OCTET STRING (SIZE(255))
				ACCESS		read-only
				STATUS		mandatory
				DESCRIPTION "Serial Number"
				::=			{ solSystemProductInfo 4 }
				
	SwDate OBJECT-TYPE
				SYNTAX		OCTET STRING (SIZE(255))
				ACCESS		read-only
				STATUS		mandatory
				DESCRIPTION "SwDate"
				::=			{ solSystemProductInfo 5 }
				
	HwVersion OBJECT-TYPE
				SYNTAX		OCTET STRING (SIZE(255))
				ACCESS		read-only
				STATUS		mandatory
				DESCRIPTION "HwVersion"
				::=			{ solSystemProductInfo 6 }

	SwVersion OBJECT-TYPE
				SYNTAX		OCTET STRING (SIZE(255))
				ACCESS		read-only
				STATUS		mandatory
				DESCRIPTION "SwVersion"
				::=			{ solSystemProductInfo 7 }
				
-- Sensors
	sensor OBJECT IDENTIFIER ::= { sol 2 }
	
	sensorTable OBJECT IDENTIFIER ::= { sensor 1 }
	
	sensorIndex OBJECT IDENTIFIER ::= { sensorTable 1 }
	
	sensor1Index OBJECT-TYPE
		SYNTAX INTEGER (1..6)
		MAX-ACCESS read-only
		STATUS mandatory
		DESCRIPTION
			"Index 1"
		::= { sensorIndex 1 }
		
	sensor2Index OBJECT-TYPE
		SYNTAX INTEGER (1..6)
		MAX-ACCESS read-only
		STATUS mandatory
		DESCRIPTION
			"Index 2"
		::= { sensorIndex 2 }
		
	sensor3Index OBJECT-TYPE
		SYNTAX INTEGER (1..6)
		MAX-ACCESS read-only
		STATUS mandatory
		DESCRIPTION
			"Index 3"
		::= { sensorIndex 3 }
		
	sensor4Index OBJECT-TYPE
		SYNTAX INTEGER (1..6)
		MAX-ACCESS read-only
		STATUS mandatory
		DESCRIPTION
			"Index 4"
		::= { sensorIndex 4 }

	sensor5Index OBJECT-TYPE
		SYNTAX INTEGER (1..6)
		MAX-ACCESS read-only
		STATUS mandatory
		DESCRIPTION
			"Index 5"
		::= { sensorIndex 5 }
		
	sensor6Index OBJECT-TYPE
		SYNTAX INTEGER (1..6)
		MAX-ACCESS read-only
		STATUS mandatory
		DESCRIPTION
			"Index 6"
		::= { sensorIndex 6 }
	
	--node type
	type OBJECT IDENTIFIER ::= { sensorTable 2 }
	sensor1Type OBJECT-TYPE
		SYNTAX INTEGER (1..2)
		MAX-ACCESS read-only
		STATUS mandatory
		DESCRIPTION
		"type 1"
		::= { type 1 }
		
	sensor2Type OBJECT-TYPE
		SYNTAX INTEGER (1..2)
		MAX-ACCESS read-only
		STATUS mandatory
		DESCRIPTION
		"type 2"
		::= { type 2 }
		
	sensor3Type OBJECT-TYPE
		SYNTAX INTEGER (1..2)
		MAX-ACCESS read-only
		STATUS mandatory
		DESCRIPTION
		"type 3"
		::= { type 3 }
	
	sensor4Type OBJECT-TYPE
		SYNTAX INTEGER (1..2)
		MAX-ACCESS read-only
		STATUS mandatory
		DESCRIPTION
		"type 4"
		::= { type 4 }
		
	sensor5Type OBJECT-TYPE
		SYNTAX INTEGER (1..2)
		MAX-ACCESS read-only
		STATUS mandatory
		DESCRIPTION
		"type 5"
		::= { type 5 }
	
	sensor6Type OBJECT-TYPE
		SYNTAX INTEGER (1..2)
		MAX-ACCESS read-only
		STATUS mandatory
		DESCRIPTION
		"type 6"
		::= { type 6 }
		
	--node subType
	subType OBJECT IDENTIFIER ::= { sensorTable 3 }
	sensor1SubType OBJECT-TYPE
		SYNTAX INTEGER (1..3)
		MAX-ACCESS read-only
		STATUS mandatory
		DESCRIPTION
		"subType 1"
		::= { subType 1 }
		
	sensor2SubType OBJECT-TYPE
		SYNTAX INTEGER (1..3)
		MAX-ACCESS read-only
		STATUS mandatory
		DESCRIPTION
		"subType 2"
		::= { subType 2 }
		
	sensor3SubType OBJECT-TYPE
		SYNTAX INTEGER (1..3)
		MAX-ACCESS read-only
		STATUS mandatory
		DESCRIPTION
		"subType 3"
		::= { subType 3 }
	
	sensor4SubType OBJECT-TYPE
		SYNTAX INTEGER (1..3)
		MAX-ACCESS read-only
		STATUS mandatory
		DESCRIPTION
		"subType 4"
		::= { subType 4 }
		
	sensor5SubType OBJECT-TYPE
		SYNTAX INTEGER (1..3)
		MAX-ACCESS read-only
		STATUS mandatory
		DESCRIPTION
		"subType 5"
		::= { subType 5 }
	
	sensor6SubType OBJECT-TYPE
		SYNTAX INTEGER (1..3)
		MAX-ACCESS read-only
		STATUS mandatory
		DESCRIPTION
		"subType 6"
		::= { subType 6 }
		
	--node enable
	enable OBJECT IDENTIFIER ::= { sensorTable 4 }
	sensor1Enable OBJECT-TYPE
		SYNTAX INTEGER (0..1)
		MAX-ACCESS read-only
		STATUS mandatory
		DESCRIPTION
		"enable 1"
		::= { enable 1 }
		
	sensor2Enable OBJECT-TYPE
		SYNTAX INTEGER (0..1)
		MAX-ACCESS read-only
		STATUS mandatory
		DESCRIPTION
		"enable 2"
		::= { enable 2 }
		
	sensor3Enable OBJECT-TYPE
		SYNTAX INTEGER (0..1)
		MAX-ACCESS read-only
		STATUS mandatory
		DESCRIPTION
		"enable 3"
		::= { enable 3 }
	
	sensor4Enable OBJECT-TYPE
		SYNTAX INTEGER (0..1)
		MAX-ACCESS read-only
		STATUS mandatory
		DESCRIPTION
		"enable 4"
		::= { enable 4 }
		
	sensor5Enable OBJECT-TYPE
		SYNTAX INTEGER (0..1)
		MAX-ACCESS read-only
		STATUS mandatory
		DESCRIPTION
		"enable 5"
		::= { enable 5 }
	
	sensor6Enable OBJECT-TYPE
		SYNTAX INTEGER (0..1)
		MAX-ACCESS read-only
		STATUS mandatory
		DESCRIPTION
		"enable 6"
		::= { enable 6 }

	--node current
	sensorCurrent OBJECT IDENTIFIER ::= { sensorTable 5 }
	sensor1Current OBJECT-TYPE
		SYNTAX INTEGER
		MAX-ACCESS read-only
		STATUS mandatory
		DESCRIPTION
		"current 1"
		::= { sensorCurrent 1 }
		
	sensor2Current OBJECT-TYPE
		SYNTAX INTEGER
		MAX-ACCESS read-only
		STATUS mandatory
		DESCRIPTION
		"current 2"
		::= { sensorCurrent 2 }
		
	sensor3Current OBJECT-TYPE
		SYNTAX INTEGER
		MAX-ACCESS read-only
		STATUS mandatory
		DESCRIPTION
		"current 3"
		::= { sensorCurrent 3 }
	
	sensor4Current OBJECT-TYPE
		SYNTAX INTEGER
		MAX-ACCESS read-only
		STATUS mandatory
		DESCRIPTION
		"current 4"
		::= { sensorCurrent 4 }
		
	sensor5Current OBJECT-TYPE
		SYNTAX INTEGER
		MAX-ACCESS read-only
		STATUS mandatory
		DESCRIPTION
		"current 5"
		::= { sensorCurrent 5 }
	
	sensor6Current OBJECT-TYPE
		SYNTAX INTEGER
		MAX-ACCESS read-only
		STATUS mandatory
		DESCRIPTION
		"current 6"
		::= { sensorCurrent 6 }
		
	--node upper
	upper OBJECT IDENTIFIER ::= { sensorTable 6 }
	sensor1Upper OBJECT-TYPE
		SYNTAX INTEGER
		MAX-ACCESS read-write
		STATUS mandatory
		DESCRIPTION
		"upper 1"
		::= { upper 1 }
		
	sensor2Upper OBJECT-TYPE
		SYNTAX INTEGER
		MAX-ACCESS read-write
		STATUS mandatory
		DESCRIPTION
		"upper 2"
		::= { upper 2 }
		
	sensor3Upper OBJECT-TYPE
		SYNTAX INTEGER
		MAX-ACCESS read-write
		STATUS mandatory
		DESCRIPTION
		"upper 3"
		::= { upper 3 }
	
	sensor4Upper OBJECT-TYPE
		SYNTAX INTEGER
		MAX-ACCESS read-write
		STATUS mandatory
		DESCRIPTION
		"upper 4"
		::= { upper 4 }
		
	sensor5Upper OBJECT-TYPE
		SYNTAX INTEGER
		MAX-ACCESS read-write
		STATUS mandatory
		DESCRIPTION
		"upper 5"
		::= { upper 5 }
	
	sensor6Upper OBJECT-TYPE
		SYNTAX INTEGER
		MAX-ACCESS read-write
		STATUS mandatory
		DESCRIPTION
		"upper 6"
		::= { upper 6 }
		
	--node lower
	lower OBJECT IDENTIFIER ::= { sensorTable 7 }
	sensor1Lower OBJECT-TYPE
		SYNTAX INTEGER
		MAX-ACCESS read-write
		STATUS mandatory
		DESCRIPTION
		"lower 1"
		::= { lower 1 }
		
	sensor2Lower OBJECT-TYPE
		SYNTAX INTEGER
		MAX-ACCESS read-write
		STATUS mandatory
		DESCRIPTION
		"lower 2"
		::= { lower 2 }
		
	sensor3Lower OBJECT-TYPE
		SYNTAX INTEGER
		MAX-ACCESS read-write
		STATUS mandatory
		DESCRIPTION
		"lower 3"
		::= { lower 3 }
	
	sensor4Lower OBJECT-TYPE
		SYNTAX INTEGER
		MAX-ACCESS read-write
		STATUS mandatory
		DESCRIPTION
		"lower 4"
		::= { lower 4 }
		
	sensor5Lower OBJECT-TYPE
		SYNTAX INTEGER
		MAX-ACCESS read-write
		STATUS mandatory
		DESCRIPTION
		"lower 5"
		::= { lower 5 }
	
	sensor6Lower OBJECT-TYPE
		SYNTAX INTEGER
		MAX-ACCESS read-write
		STATUS mandatory
		DESCRIPTION
		"lower 6"
		::= { lower 6 }
		
	--node upperMax
	upperMax OBJECT IDENTIFIER ::= { sensorTable 8 }
	sensor1UpperMax OBJECT-TYPE
		SYNTAX INTEGER
		MAX-ACCESS read-only
		STATUS mandatory
		DESCRIPTION
		"upperMax 1"
		::= { upperMax 1 }
		
	sensor2UpperMax OBJECT-TYPE
		SYNTAX INTEGER
		MAX-ACCESS read-only
		STATUS mandatory
		DESCRIPTION
		"upperMax 2"
		::= { upperMax 2 }
		
	sensor3UpperMax OBJECT-TYPE
		SYNTAX INTEGER
		MAX-ACCESS read-only
		STATUS mandatory
		DESCRIPTION
		"upperMax 3"
		::= { upperMax 3 }
	
	sensor4UpperMax OBJECT-TYPE
		SYNTAX INTEGER
		MAX-ACCESS read-only
		STATUS mandatory
		DESCRIPTION
		"upperMax 4"
		::= { upperMax 4 }
		
	sensor5UpperMax OBJECT-TYPE
		SYNTAX INTEGER
		MAX-ACCESS read-only
		STATUS mandatory
		DESCRIPTION
		"upperMax 5"
		::= { upperMax 5 }
	
	sensor6UpperMax OBJECT-TYPE
		SYNTAX INTEGER
		MAX-ACCESS read-only
		STATUS mandatory
		DESCRIPTION
		"upperMax 6"
		::= { upperMax 6 }
		
	--node lowerMin
	lowerMin OBJECT IDENTIFIER ::= { sensorTable 9 }
	sensor1LowerMin OBJECT-TYPE
		SYNTAX INTEGER
		MAX-ACCESS read-only
		STATUS mandatory
		DESCRIPTION
		"lowerMin 1"
		::= { lowerMin 1 }
		
	sensor2LowerMin OBJECT-TYPE
		SYNTAX INTEGER
		MAX-ACCESS read-only
		STATUS mandatory
		DESCRIPTION
		"lowerMin 2"
		::= { lowerMin 2 }
		
	sensor3LowerMin OBJECT-TYPE
		SYNTAX INTEGER
		MAX-ACCESS read-only
		STATUS mandatory
		DESCRIPTION
		"lowerMin 3"
		::= { lowerMin 3 }
	
	sensor4LowerMin OBJECT-TYPE
		SYNTAX INTEGER
		MAX-ACCESS read-only
		STATUS mandatory
		DESCRIPTION
		"lowerMin 4"
		::= { lowerMin 4 }
		
	sensor5LowerMin OBJECT-TYPE
		SYNTAX INTEGER
		MAX-ACCESS read-only
		STATUS mandatory
		DESCRIPTION
		"lowerMin 5"
		::= { lowerMin 5 }
	
	sensor6LowerMin OBJECT-TYPE
		SYNTAX INTEGER
		MAX-ACCESS read-only
		STATUS mandatory
		DESCRIPTION
		"lowerMin 6"
		::= { lowerMin 6 }		
			
	--node sensorMin
	sensorMin OBJECT IDENTIFIER ::= { sensorTable 10 }
	sensor1SensorMin OBJECT-TYPE
		SYNTAX INTEGER
		MAX-ACCESS read-only
		STATUS mandatory
		DESCRIPTION
		"sensorMin 1"
		::= { sensorMin 1 }
		
	sensor2SensorMin OBJECT-TYPE
		SYNTAX INTEGER
		MAX-ACCESS read-only
		STATUS mandatory
		DESCRIPTION
		"sensorMin 2"
		::= { sensorMin 2 }
		
	sensor3SensorMin OBJECT-TYPE
		SYNTAX INTEGER
		MAX-ACCESS read-only
		STATUS mandatory
		DESCRIPTION
		"sensorMin 3"
		::= { sensorMin 3 }
	
	sensor4SensorMin OBJECT-TYPE
		SYNTAX INTEGER
		MAX-ACCESS read-only
		STATUS mandatory
		DESCRIPTION
		"sensorMin 4"
		::= { sensorMin 4 }
		
	sensor5SensorMin OBJECT-TYPE
		SYNTAX INTEGER
		MAX-ACCESS read-only
		STATUS mandatory
		DESCRIPTION
		"sensorMin 5"
		::= { sensorMin 5 }
	
	sensor6SensorMin OBJECT-TYPE
		SYNTAX INTEGER
		MAX-ACCESS read-only
		STATUS mandatory
		DESCRIPTION
		"sensorMin 6"
		::= { sensorMin 6 }
			
	--node sensorMax
	sensorMax OBJECT IDENTIFIER ::= { sensorTable 11 }
	sensor1SensorMax OBJECT-TYPE
		SYNTAX INTEGER
		MAX-ACCESS read-only
		STATUS mandatory
		DESCRIPTION
		"sensorMax 1"
		::= { sensorMax 1 }
		
	sensor2SensorMax OBJECT-TYPE
		SYNTAX INTEGER
		MAX-ACCESS read-only
		STATUS mandatory
		DESCRIPTION
		"sensorMax 2"
		::= { sensorMax 2 }
		
	sensor3SensorMax OBJECT-TYPE
		SYNTAX INTEGER
		MAX-ACCESS read-only
		STATUS mandatory
		DESCRIPTION
		"sensorMax 3"
		::= { sensorMax 3 }
	
	sensor4SensorMax OBJECT-TYPE
		SYNTAX INTEGER
		MAX-ACCESS read-only
		STATUS mandatory
		DESCRIPTION
		"sensorMax 4"
		::= { sensorMax 4 }
		
	sensor5SensorMax OBJECT-TYPE
		SYNTAX INTEGER
		MAX-ACCESS read-only
		STATUS mandatory
		DESCRIPTION
		"sensorMax 5"
		::= { sensorMax 5 }
	
	sensor6SensorMax OBJECT-TYPE
		SYNTAX INTEGER
		MAX-ACCESS read-only
		STATUS mandatory
		DESCRIPTION
		"sensorMax 6"
		::= { sensorMax 6 }
		
	--node status
	status OBJECT IDENTIFIER ::= { sensorTable 12 }
	sensor1Status OBJECT-TYPE
		SYNTAX INTEGER
		MAX-ACCESS read-only
		STATUS mandatory
		DESCRIPTION
		"status 1"
		::= { status 1 }
		
	sensor2Status OBJECT-TYPE
		SYNTAX INTEGER
		MAX-ACCESS read-only
		STATUS mandatory
		DESCRIPTION
		"status 2"
		::= { status 2 }
		
	sensor3Status OBJECT-TYPE
		SYNTAX INTEGER
		MAX-ACCESS read-only
		STATUS mandatory
		DESCRIPTION
		"status 3"
		::= { status 3 }
	
	sensor4Status OBJECT-TYPE
		SYNTAX INTEGER
		MAX-ACCESS read-only
		STATUS mandatory
		DESCRIPTION
		"status 4"
		::= { status 4 }
		
	sensor5Status OBJECT-TYPE
		SYNTAX INTEGER
		MAX-ACCESS read-only
		STATUS mandatory
		DESCRIPTION
		"status 5"
		::= { status 5 }
	
	sensor6Status OBJECT-TYPE
		SYNTAX INTEGER
		MAX-ACCESS read-only
		STATUS mandatory
		DESCRIPTION
		"status 6"
		::= { status 6 }

	--node UpperMaxLimit
	upperMaxLimit OBJECT IDENTIFIER ::= { sensorTable 13 }
	sensor1UpperMaxLimit OBJECT-TYPE
		SYNTAX INTEGER
		MAX-ACCESS read-only
		STATUS mandatory
		DESCRIPTION
		"upperMaxLimit 1"
		::= { upperMaxLimit 1 }
		
	sensor2UpperMaxLimit OBJECT-TYPE
		SYNTAX INTEGER
		MAX-ACCESS read-only
		STATUS mandatory
		DESCRIPTION
		"upperMaxLimit 2"
		::= { upperMaxLimit 2 }
		
	sensor3UpperMaxLimit OBJECT-TYPE
		SYNTAX INTEGER
		MAX-ACCESS read-only
		STATUS mandatory
		DESCRIPTION
		"upperMaxLimit 3"
		::= { upperMaxLimit 3 }
	
	sensor4UpperMaxLimit OBJECT-TYPE
		SYNTAX INTEGER
		MAX-ACCESS read-only
		STATUS mandatory
		DESCRIPTION
		"upperMaxLimit 4"
		::= { upperMaxLimit 4 }
		
	sensor5UpperMaxLimit OBJECT-TYPE
		SYNTAX INTEGER
		MAX-ACCESS read-only
		STATUS mandatory
		DESCRIPTION
		"upperMaxLimit 5"
		::= { upperMaxLimit 5 }
	
	sensor6UpperMaxLimit OBJECT-TYPE
		SYNTAX INTEGER
		MAX-ACCESS read-only
		STATUS mandatory
		DESCRIPTION
		"upperMaxLimit 6"
		::= { upperMaxLimit 6 }
	
-- Discs
	disc OBJECT IDENTIFIER ::= { sol 3 }
	
	discTable OBJECT IDENTIFIER ::= { disc 1 }
	
	discIndex OBJECT IDENTIFIER ::= { discTable 1 }
	
	disc1Index OBJECT-TYPE
		SYNTAX Integer32
		MAX-ACCESS read-write
		STATUS current
		DESCRIPTION
			"Index 1"
		::= { discIndex 1 }
		
	disc2Index OBJECT-TYPE
		SYNTAX Integer32
		MAX-ACCESS read-write
		STATUS current
		DESCRIPTION
			"Index 2"
		::= { discIndex 2 }
		
	disc3Index OBJECT-TYPE
		SYNTAX Integer32
		MAX-ACCESS read-write
		STATUS current
		DESCRIPTION
			"Index 3"
		::= { discIndex 3 }
		
	disc4Index OBJECT-TYPE
		SYNTAX Integer32
		MAX-ACCESS read-write
		STATUS current
		DESCRIPTION
			"Index 4"
		::= { discIndex 4 }
	
	--node isOk
	ok OBJECT IDENTIFIER ::= { discTable 2 }
	disc1Ok OBJECT-TYPE
		SYNTAX Integer32
		MAX-ACCESS read-write
		STATUS current
		DESCRIPTION
			"ok 1"
		::= { ok 1 }
		
	disc2Ok OBJECT-TYPE
		SYNTAX Integer32
		MAX-ACCESS read-write
		STATUS current
		DESCRIPTION
			"ok 2"
		::= { ok 2 }
		
	disc3Ok OBJECT-TYPE
		SYNTAX Integer32
		MAX-ACCESS read-write
		STATUS current
		DESCRIPTION
			"ok 3"
		::= { ok 3 }
		
	disc4Ok OBJECT-TYPE
		SYNTAX Integer32
		MAX-ACCESS read-write
		STATUS current
		DESCRIPTION
			"ok 4"
		::= { ok 4 }

   --node isIDE
	ide OBJECT IDENTIFIER ::= { discTable 3 }
	disc1IDE OBJECT-TYPE
		SYNTAX Integer32
		MAX-ACCESS read-write
		STATUS current
		DESCRIPTION
			"ide 1"
		::= { ide 1 }
		
	disc2IDE OBJECT-TYPE
		SYNTAX Integer32
		MAX-ACCESS read-write
		STATUS current
		DESCRIPTION
			"ide 2"
		::= { ide 2 }
		
	disc3IDE OBJECT-TYPE
		SYNTAX Integer32
		MAX-ACCESS read-write
		STATUS current
		DESCRIPTION
			"ide 3"
		::= { ide 3 }
		
	disc4IDE OBJECT-TYPE
		SYNTAX Integer32
		MAX-ACCESS read-write
		STATUS current
		DESCRIPTION
			"ide 4"
		::= { ide 4 }

	--node isSMART
	smart OBJECT IDENTIFIER ::= { discTable 4 }
	disc1SMART OBJECT-TYPE
		SYNTAX Integer32
		MAX-ACCESS read-write
		STATUS current
		DESCRIPTION
			"SMART 1"
		::= { smart 1 }
		
	disc2SMART OBJECT-TYPE
		SYNTAX Integer32
		MAX-ACCESS read-write
		STATUS current
		DESCRIPTION
			"SMART 2"
		::= { smart 2 }
		
	disc3SMART OBJECT-TYPE
		SYNTAX Integer32
		MAX-ACCESS read-write
		STATUS current
		DESCRIPTION
			"SMART 3"
		::= { smart 3 }
		
	disc4SMART OBJECT-TYPE
		SYNTAX Integer32
		MAX-ACCESS read-write
		STATUS current
		DESCRIPTION
			"SMART 4"
		::= { smart 4 }
		
	--node ModelNumber
	modelNumber OBJECT IDENTIFIER ::= { discTable 11 }
	disc1ModelNumber OBJECT-TYPE
		SYNTAX       OCTET STRING (SIZE (40))
        ACCESS       read-only
        STATUS       mandatory        
		DESCRIPTION
			"ModelNumber 1"
		::= { modelNumber 1 }
		
	disc2ModelNumber OBJECT-TYPE
		SYNTAX       OCTET STRING (SIZE (40))
        ACCESS       read-only
        STATUS       mandatory        
		DESCRIPTION
		"ModelNumber 2"
		::= { modelNumber 2 }
		
	disc3ModelNumber OBJECT-TYPE
		SYNTAX       OCTET STRING (SIZE (40))
        ACCESS       read-only
        STATUS       mandatory        
		DESCRIPTION
		"ModelNumber 3"
		::= { modelNumber 3 }
		
	disc4ModelNumber OBJECT-TYPE
		SYNTAX       OCTET STRING (SIZE (40))
        ACCESS       read-only
        STATUS       mandatory        
		DESCRIPTION
			"ModelNumber 4"
		::= { modelNumber 4 }
		
	--node FirmwareRevision
	firmwareRevision OBJECT IDENTIFIER ::= { discTable 12 }
	disc1FirmwareRevision OBJECT-TYPE
		SYNTAX       OCTET STRING (SIZE (8))
        ACCESS       read-only
        STATUS       mandatory        
		DESCRIPTION
			"FirmwareRevision 1"
		::= { firmwareRevision 1 }
		
	disc2FirmwareRevision OBJECT-TYPE
		SYNTAX       OCTET STRING (SIZE (8))
        ACCESS       read-only
        STATUS       mandatory        
		DESCRIPTION
		"FirmwareRevision 2"
		::= { firmwareRevision 2 }
		
	disc3FirmwareRevision OBJECT-TYPE
		SYNTAX       OCTET STRING (SIZE (8))
        ACCESS       read-only
        STATUS       mandatory        
		DESCRIPTION
		"FirmwareRevision 3"
		::= { firmwareRevision 3 }
		
	disc4FirmwareRevision OBJECT-TYPE
		SYNTAX       OCTET STRING (SIZE (8))
        ACCESS       read-only
        STATUS       mandatory        
		DESCRIPTION
		"FirmwareRevision 4"
		::= { firmwareRevision 4 }

	--node SerialNumber
	serialNumber OBJECT IDENTIFIER ::= { discTable 13 }
	disc1SerialNumber OBJECT-TYPE
		SYNTAX       OCTET STRING (SIZE (20))
        ACCESS       read-only
        STATUS       mandatory        
		DESCRIPTION
			"SerialNumber 1"
		::= { serialNumber 1 }
		
	disc2SerialNumber OBJECT-TYPE
		SYNTAX       OCTET STRING (SIZE (20))
        ACCESS       read-only
        STATUS       mandatory        
		DESCRIPTION
		"SerialNumber 2"
		::= { serialNumber 2 }
		
	disc3SerialNumber OBJECT-TYPE
		SYNTAX       OCTET STRING (SIZE (20))
        ACCESS       read-only
        STATUS       mandatory        
		DESCRIPTION
		"SerialNumber 3"
		::= { serialNumber 3 }
		
	disc4SerialNumber OBJECT-TYPE
		SYNTAX       OCTET STRING (SIZE (20))
        ACCESS       read-only
        STATUS       mandatory        
		DESCRIPTION
		"SerialNumber 4"
		::= { serialNumber 4 }
                                     
                                     
-- end sol
    solEndMarker OBJECT-TYPE
                 SYNTAX       INTEGER (0..1)
                 ACCESS       read-only
                 STATUS       mandatory
                 DESCRIPTION  "End marker (for convenience)."
                 ::=          { solEnd 1 }

-- Traps
    somHeartbeat TRAP-TYPE
	    ENTERPRISE sol
		DESCRIPTION "Heartbeat failed."
		::= 1

    somInterrupt TRAP-TYPE
	    ENTERPRISE sol
		DESCRIPTION "SOM driver interrupt occurred."
		::= 2

    somCreateThreadError TRAP-TYPE
	    ENTERPRISE sol
		DESCRIPTION "SOM driver create-thread-error occurred."
		::= 3

    somIOCTLError TRAP-TYPE
	    ENTERPRISE sol
		DESCRIPTION "SOM driver IOCTL-error occurred."
		::= 4

    somWatchdog TRAP-TYPE
	    ENTERPRISE sol
		DESCRIPTION "SOM watchdog timeout occurred."
		::= 5
	
	solRevision TRAP-TYPE
		ENTERPRISE sol
		VARIABLES { systemRevisionHours, systemRevisionText }
		DESCRIPTION "PC DiagMonitor Operating Hours Revision"
		::=6

END -- SOL-MIB DEFINITIONS

----------------------------------------------------------------------------
